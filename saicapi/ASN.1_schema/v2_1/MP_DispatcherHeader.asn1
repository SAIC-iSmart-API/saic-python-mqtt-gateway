MPDispatcherHeaderModule

DEFINITIONS
AUTOMATIC TAGS ::= 
BEGIN
MPDispatcherHeader ::= SEQUENCE
{
  dispatcherBodyEncoding INTEGER(0..2),
  dispatcherMessageLength INTEGER(0..255),
  protocolVersion INTEGER(0..255)
}

END
